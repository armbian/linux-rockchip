-- SPDX-License-Identifier: BSD-3-Clause
--
-- Copyright (c) 2024 Rockchip Electronics Co., Ltd.

ECDSASignature ::= SEQUENCE {
	x	INTEGER ({ rkce_ecc_get_signature_r }),
	y	INTEGER ({ rkce_ecc_get_signature_s })
}
